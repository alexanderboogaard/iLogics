'03-12-2020 - AB - Added additional check, so errors are ignored

Sub Main()

Break

    If iProperties.Value("Custom", "PTC_WM_LIFECYCLE_STATE") = "RELEASED" Then
        Exit Sub
    Else
        Try
            Try
                TryLength = iProperties.Value("Custom", "MAINPROFILE")
            Catch
                iProperties.Value("Custom", "MAINPROFILE") = ""
            End Try


            Try
                TryLength = iProperties.Value("Custom", "PTC_WM_NAME")
            Catch
                iProperties.Value("Custom", "PTC_WM_NAME") = "Temp"
            End Try


            If ThisDoc.FileName(True) <> "" Then
                iProperties.Value("Custom", "PTC_WM_NUMBER") = ThisDoc.FileName(True)
            Else
                iProperties.Value("Custom", "PTC_WM_NUMBER") = "Temp.Not"
            End If

            If ThisDoc.FileName(True) <> "" Then
                iProperties.Value("Custom", "PTC_WM_PART_NUMBER") = ThisDoc.FileName(False)
            Else
                iProperties.Value("Custom", "PTC_WM_PART_NUMBER") = "Temp.Not"
            End If

            Try
                TryLength = iProperties.Value("Custom", "PAINTAREA")
            Catch
                iProperties.Value("Custom", "PAINTAREA") = ""
            End Try

            Dim oAsmDoc As AssemblyDocument
            Dim oMyParameter As UserParameters
            oAsmDoc = ThisDoc.Document
            oMyParameter = oAsmDoc.ComponentDefinition.Parameters.UserParameters

            Try
                TryLength = Parameter("JBCONSERVATION")
            Catch
                oParameter = oMyParameter.AddByValue("JBCONSERVATION", "None", UnitsTypeEnum.kTextUnits)
                MultiValue.SetList("JBCONSERVATION", "None", "Hot dip galvanised", "Painted", "Painted (zinc silicate 50-80ųm)", "Sherardised", "TSA", "TS ZnAl 85-15", "Zinc plated (electrolytic)")
            End Try

            Try
                TryLength = Parameter("JBEXECUTIONCLASS")
            Catch
                oParameter = oMyParameter.AddByValue("JBEXECUTIONCLASS", "", UnitsTypeEnum.kTextUnits)
                MultiValue.SetList("JBEXECUTIONCLASS", "", "EXC 1", "EXC 2", "EXC 3", "EXC 4")
            End Try

            Try
                TryLength = Parameter("JBSORT")
            Catch
                oParameter = oMyParameter.AddByValue("JBSORT", "", UnitsTypeEnum.kTextUnits)
                MultiValue.SetList("JBSORT", "", "Abutment", "Balance beam", "Bearing", "Bracing", "Bridge section", "Cable bracket", "Clamp", "Cover", "Deck", "Fastener", "Footwalk", "Guardrail", "Launching", "Lifting", "Panel", "Pillar", "Pin", "Plate", "Platform", "Profile", "Ramp", "Reinforcement", "Screen", "Seismic Restraint", "Stair", "Support beam", "Tool", "Transom", "U-frame", "Water management")
            End Try


            Try
                TryLength = Parameter("JBMaterial")
            Catch
                oParameter = oMyParameter.AddByValue("JBMaterial", "", UnitsTypeEnum.kTextUnits)
                MultiValue.SetList("JBMaterial", "", "Undefined", "4", "8", "12", "4.6", "8.8", "10.9", "10HV", "12.9", "140HV", "200HV", "350+80 HV30", "34CrNiMo6V", "35Mn6No3", "42CrMo4", "42CrMo4+QT", "708M40", "AL99.5 HH", "AlMg1 H14/H24", "AlMg3", "AlMg3 HH", "AlMg4.5 MN", "AlMgSi0.5", "AlMgSi1", "C10", "C22N", "C25/30", "C28/35", "CR", "DX51+Z275", "E470", "Hardox 400", "HDPE", "LDPE", "PE-HM", "Pinewood", "Plywood", "PTFE", "Polyethyleenterefalaat (PET)", "S235", "S235JR", "S235JRH", "S235J0", "S235J2", "S275", "S275JR", "S275J0", "S275J0H", "S275J2", "S275N", "S275NL", "S275M", "S275ML", "S355", "S355JR", "S355J0", "S355J2", "S355J2H", "S355K2", "S355N", "S355NL", "S355M", "S355ML", "S420", "S420N", "S355NH", "S420NL", "S420M", "S420ML", "S460", "S460N", "S460NL", "S460M", "S460MC", "S460ML", "SAPELE", "    X2 CrNiMo 17 12 2 (316L)", "X5 CrNi 18 10", "X5 CrNiMo 17 12 2", "X6 CrNi 18 10", "X6 CrNiMo 17 12 2", "TECLITE100M")
            End Try

            Try
                TryLength = Parameter("BOMStrucType")
            Catch
                oParameter = oMyParameter.AddByValue("BOMStrucType", "Inseparable", UnitsTypeEnum.kTextUnits)
                MultiValue.SetList("BOMStrucType", "Separable", "Phantom", "Reference", "Inseparable")
            End Try



            iProperties.Value("Project", "Part Number") = Left(iProperties.Value("Custom", "PTC_WM_NUMBER"), Len(iProperties.Value("Custom", "PTC_WM_NUMBER")) - 4)

            iProperties.Value("Custom", "CONSERVATION") = Parameter("JBCONSERVATION")

            iProperties.Value("Custom", "EXECUTIONCLASS") = Parameter("JBEXECUTIONCLASS")
            If iProperties.Value("Custom", "EXECUTIONCLASS") = "" Then
                iProperties.Value("Custom", "EXECUTIONCLASSNR") = ""
                iProperties.Value("Custom", "EXECUTIONCLASSNR_NL") = ""
            Else
                iProperties.Value("Custom", "EXECUTIONCLASSNR") = "Execution class " + Right(Parameter("JBEXECUTIONCLASS"), 1) + " (EN 1090)"
                iProperties.Value("Custom", "EXECUTIONCLASSNR_NL") = "Uitvoeringsklasse " + Right(Parameter("JBEXECUTIONCLASS"), 1) + " (EN 1090)"
            End If


            iProperties.Value("Custom", "JBPARTDESCRIPTION") = iProperties.Value("Project", "Description")

            iProperties.Value("Custom", "MATERIAL") = Parameter("JBMaterial")

            iProperties.Value("Custom", "SORT") = Parameter("JBSORT")

            iProperties.Value("Summary", "Title") = iProperties.Value("Custom", "PTC_WM_NAME")

            WeightTemp = Round(iProperties.Mass, 2)
            If WeightTemp = 0 Then
                WeightTemp = Round(iProperties.Mass, 3)
            End If
            If WeightTemp = 0 Then
                WeightTemp = Round(iProperties.Mass, 4)
            End If
            If WeightTemp = 0 Then
                WeightTemp = Round(iProperties.Mass, 5)
            End If




            If Parameter("JBCONSERVATION") = "Hot dip galvanised" Then
                iProperties.Value("Custom", "WEIGHT") = Round((WeightTemp * 1.04), 1)
            Else
                iProperties.Value("Custom", "WEIGHT") = Round(WeightTemp, 1)


            End If
            Try
                ' Get part component definition
                Dim oAsmCompDef As AssemblyComponentDefinition
                oAsmCompDef = ThisDoc.Document.ComponentDefinition


                Select Case Parameter("BOMStrucType")

                    Case "Separable"
                        'is normal document type
                        oAsmCompDef.BOMStructure = "51970"
                        iProperties.Value("Custom", "partType") = "separable"
                    Case "Phantom"
                        oAsmCompDef.BOMStructure = "51971"
                        iProperties.Value("Custom", "partType") = "inseparable"
                    Case "Reference"
                        oAsmCompDef.BOMStructure = "51972"
                        iProperties.Value("Custom", "partType") = "inseparable"
                    Case "Purchased"
                        oAsmCompDef.BOMStructure = "51973"
						iProperties.Value("Custom", "partType") = "inseparable"
                    Case "Inseparable"
                        oAsmCompDef.BOMStructure = "51974"
                        iProperties.Value("Custom", "partType") = "inseparable"
                End Select

            Catch
            End Try

            oAsmDoc = Nothing
            oMyParameter = Nothing

        Catch
        End Try
    End If
End Sub
