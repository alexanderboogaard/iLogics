Sub Main()
    On Error GoTo StopRule

    Dim oDoc As DrawingDocument
    oDoc = ThisDoc.Document

    Dim oViewlabel, oViewlabel1 As DrawingViewLabel
    Dim LabelBox, LabelBox1 As Box2d
    Dim LabelPoint, LabelPoint1 As Point2d

    oViewlabel1 = ThisApplication.CommandManager.Pick(SelectionFilterEnum.kDrawingViewLabelFilter, "Select first view label to align other view labels to")
    LabelBox1 = oViewlabel1.RangeBox

    For i = 0 To 100
        On Error GoTo StopRule
        oViewlabel = ThisApplication.CommandManager.Pick(SelectionFilterEnum.kDrawingViewLabelFilter, "Select view label to align")
        LabelPoint = oViewlabel.Position()
        LabelBox = oViewlabel.RangeBox
        LabelPoint.Y = LabelPoint.Y + (LabelBox1.MinPoint.Y - LabelBox.MinPoint.Y)
        oViewlabel.Position = LabelPoint
    Next
StopRule:
End Sub
'
'Private Function GetViewLabel1(ByVal oDoc As DrawingDocument) As DrawingViewLabel
'Dim Viewlabel as DrawingViewLabel
'Viewlabel = ThisApplication.CommandManager.Pick(SelectionFilterEnum.kDrawingViewLabelFilter, "Select first view label to align other view labels to")
'Return Viewlabel 
'End Function
'
'Private Function GetViewLabel(ByVal oDoc As DrawingDocument) As DrawingViewLabel
'Dim Viewlabel as DrawingViewLabel
'Viewlabel = ThisApplication.CommandManager.Pick(SelectionFilterEnum.kDrawingViewLabelFilter, "Select view label to align")
'Return Viewlabel 
'End Function
'
