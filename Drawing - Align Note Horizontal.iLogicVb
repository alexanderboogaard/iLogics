Sub Main()
	undoDoc = ThisApplication.ActiveDocument
	oNamer = "align notes"
	Dim UNDO As Transaction 
	UNDO = ThisApplication.TransactionManager.StartTransaction(undoDoc, oNamer)
    
	On Error GoTo StopRule

    Dim oDoc As DrawingDocument
    oDoc = ThisDoc.Document

    Dim oDrawingNote, oDrawingNote1 As DrawingNote
    oDrawingNote1 = ThisApplication.CommandManager.Pick(SelectionFilterEnum.kDrawingNoteFilter, "Select first note to align other notes to")

    Dim NotePoint, NotePoint1 As Point2d
    NotePoint1 = oDrawingNote1.Position()

    For i = 0 To 100
        oDrawingNote = ThisApplication.CommandManager.Pick(SelectionFilterEnum.kDrawingNoteFilter, "Select note to align")
        NotePoint = oDrawingNote.Position()
        NotePoint.Y = NotePoint1.Y
        oDrawingNote.Position = NotePoint

Next
StopRule :
	UNDO.End
End Sub
